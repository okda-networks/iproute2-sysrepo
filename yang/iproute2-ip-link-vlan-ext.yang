module iproute2-ip-link-vlan-ext {
    yang-version 1.1;
    namespace "urn:okda:iproute2:ip:link:vlan:ext";
    prefix "iplinkvlan";

    import iproute2-cmdgen-extensions { prefix ipr2cgen; }
    import iproute2-ip-link {prefix iplink;}


    organization
        "Okda Networks";

    contact
        "Author: Ali Aqrabawi
        <aaqrabaw@okdanetworks.com>";

    description

        "This module contain the iproute2 'ip link' vlan type configuration ,
        this is module contains all IP-LINK(8) related configs,
        refer to https://manpages.debian.org/unstable/iproute2/ip-link.8.en.html";

    revision "2024-02-13" {
        description "Revision 1";
        reference
            "YANG model for iproute2 ip link vlan extension case.";
    }



    augment "/iplink:links/iplink:link" {
        description "adding vlan type paramters";
        container vlan {
            ipr2cgen:on-update-include "type";
            when "../iplink:type = 'iplink:vlan'";
            must "../iplink:device" {
                description "VLAN configuration requires 'device' to be set";
                error-message "VLAN configuration is not allowed without specifying 'device'";
            }
            description "vlan type interface paramters";
            leaf protocol {
                description "VLAN_PROTO - either 802.1Q or 802.1ad.";
                default "802.1q";
                type enumeration {
                    enum "802.1q";
                    enum "802.1ad";
                }
            }
            leaf id {
                type uint16;
                description "VLAN ID";
            }
            leaf reorder_hdr {
                description "{ on | off } - specifies whether ethernet headers are reordered or not (default is on).";
                type enumeration {
                    enum "on";
                    enum "off";
                }
            }
            leaf gvrp {
                description "{ on | off } - specifies whether this VLAN should be
                registered using GARP VLAN Registration Protocol.";
                type enumeration {
                    enum "on";
                    enum "off";
                }
            }
            leaf mvrp {
                description "{ on | off } - specifies whether this VLAN should be registered
                using Multiple VLAN Registration Protocol.";
                type enumeration {
                    enum "on";
                    enum "off";
                }
            }
            leaf loose_binding {
                description "{ on | off } - specifies whether the VLAN device state is bound to the
                physical device state.";
                type enumeration {
                    enum "on";
                    enum "off";
                }
            }
            leaf bridge_binding {
                description "{ on | off } - specifies whether the VLAN device link state tracks the state
                of bridge ports that are members of the VLAN.";
                type enumeration {
                    enum "on";
                    enum "off";
                }
            }
            leaf-list ingress-qos-map {
                type string {
                    pattern '\d+:\d+';
                }
                description "defines a mapping of VLAN header prio field to the Linux internal packet priority on
                incoming frames. The format is FROM:TO with multiple mappings separated by spaces.";
            }
            leaf-list egress-qos-map {
                type string {
                    pattern '\d+:\d+';
                }
                description "defines a mapping of Linux internal packet priority to VLAN header prio field but
                for outgoing frames.The format is FROM:TO with multiple mappings separated by spaces.";
            }
        }
    }

}

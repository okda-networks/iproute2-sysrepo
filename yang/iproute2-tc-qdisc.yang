module iproute2-tc-qdisc {
    yang-version 1.1;
    namespace "urn:okda:iproute2:tc:qdisc";
    prefix "qdisc";

    import okda-onmcli-extensions{ prefix onmcli; }
    import iproute2-ip-link {prefix iplink;}
    import iproute2-cmdgen-extensions { prefix ipr2cgen; }
    import iproute2-ip-netns { prefix ipnetns; }

    organization "Okda Networks";

    contact
        "Authors: Amjad Daraiseh <adaraiseh@okdanetworks.com>
        Ali Aqrabawi <aaqrabaw@okdanetworks.com>";


    description
        "This module contain the iproute2 'tc qdisc' configurations.
        This is module contains tc - show / manipulate 'queueing discipline' settings.
        refer to https://manpages.debian.org/bookworm/iproute2/tc.8.en.html";

    revision "2024-02-17" {
        description "Initial version.";
    }

    typedef parent-id {
        description "Specifies qdisc or class parent, can be specified using ID or root";
        type union {
            type leafref{
                path '/qdisc:classes/qdisc:class/qdisc:classid';
            }
            type enumeration {
                enum root {
                    description "Indicates the qdisc is at the root.";
                }
            }
            type string {
            // Temporary to allow referencing a qdisc
                pattern '[0-9a-fA-F]+:[0-9a-fA-F]+';
            }
            type string {
            // Temporary to allow referencing a qdisc
                pattern ':[0-9a-fA-F]+';
            }
        }
    }

    typedef qdisc-kind {
        type enumeration {
        // classless qdiscs
            enum "choke" {
                description "Choose and Keep for responsive flows,  a classless qdisc designed to
                both identify and penalize flows that monopolize the queue.";
            }
            enum "codel" {
                description "Controlled Delay, adaptive 'no-knobs' active queue management algorithm (AQM) scheme
                that was developed to address the shortcomings of RED and its variants.";
            }
            enum "bfifo" {
                description "Byte-limited First In, First Out queue.";
            }
            enum "pfifo" {
                description "Packet-limited First In, First Out queue.";
            }
            enum "fq" {
                description "Fair Queue Scheduler realises TCP pacing and scales to millions of concurrent flows per qdisc.";
            }
            enum "fq_codel" {
                description "Fair Queuing Controlled Delay is queuing discipline
                that combines Fair Queuing with the CoDel AQM scheme.";
            }
            enum "fq_pie" {
                description "Flow Queuing with Proportional Integral controller Enhanced, is a queuing discipline that
                combines Flow Queuing with the PIE AQM scheme.";
            }
            enum "gred" {
                description "Generalized Random Early Detection,
                combines multiple RED queues in order to achieve multiple drop priorities.";
            }
            enum "hhf" {
                description "Heavy-Hitter Filter differentiates between small flows and the opposite, heavy-hitters.
                The goal is to catch the heavy-hitters and move them to a separate queue with less priority
                so that bulk traffic does not affect the latency of critical traffic.";
            }
            enum "mqprio" {
                description "Multiqueue Priority Qdisc is a simple queuing discipline
                that allows mapping traffic flows to hardware queue ranges using priorities
                and a configurable priority to traffic class mapping.";
            }
            enum "multiq" {
                description "Multiqueue is a qdisc optimized for devices with multiple Tx queues.
                It has been added for hardware that wishes to avoid head-of-line blocking.";
            }
            enum "netem" {
                description "Network Emulator is an enhancement of the Linux traffic control
                facilities that allow one to add delay, packet loss, duplication and
                more other characteristics to packets outgoing from a selected network interface.";
            }
            enum "pfifo_fast" {
                description "Standard qdisc for 'Advanced Router' enabled kernels. Consists of a
                three-band queue which honors Type of Service flags, as well as the
                priority that may be assigned to a packet.";
            }
            enum "pie" {
                description "Proportional Integral controller-Enhanced (PIE) is a control
                theoretic active queue management scheme. It is based on the
                proportional integral controller but aims to control delay.";
            }
            enum "red" {
                description "Random Early Detection simulates physical congestion by randomly
                dropping packets when nearing configured bandwidth allocation. Well
                suited to very large bandwidth applications.";
            }
            enum "sfb" {
                description "Stochastic Fair Blue is a classless qdisc to manage congestion based
                on packet loss and link utilization history while trying to prevent
                non-responsive flows (i.e. flows that do not react to congestion
                marking or dropped packets) from impacting performance of responsive flows.";
            }
            enum "sfq" {
                description "Stochastic Fairness Queueing reorders queued traffic so each
                'session' gets to send a packet in turn.";
            }
            enum "tbf" {
                description "The Token Bucket Filter is suited for slowing traffic down to a
                precisely configured rate. Scales well to large bandwidths.";
            }
            // classful qdiscs
            enum "ATM" {
                description "Map flows to virtual circuits of an underlying asynchronous transfer
                mode device.";
            }
            enum "cbq" {
                description "";
            }
            enum "drr" {
                description "";
            }
            enum "dsmark" {
                description "";
            }
            enum "ets" {
                description "";
            }
            enum "hfsc" {
                description "";
            }
            enum "htb" {
                description "";
            }
            enum "prio" {
                description "";
            }
            enum "qfq" {
                description "";
            }
        }
        description "Defines the supported queueing discipline kinds.";
    }
    typedef bit-units {
        type string{
            pattern '\d+(\.\d+)?([tgmkTGMK]bit|bit)';
        }
    }

    grouping qdisc-stats{
        container stats {
            config false;
            leaf bytes{
                type uint32;
                description " ";
            }
            leaf packets {
                type uint32;
                description " ";
            }
            leaf drops {
                type uint32;
                description " ";
            }
            leaf overlimits {
                type uint32;
                description " ";
            }
            leaf requeues {
                type uint32;
                description " ";
            }
            leaf backlog {
                type uint32;
                description " ";
            }
            leaf qlen {
                type uint32;
                description " ";
            }
        }
    }

    grouping codel-stats{
        container codel-stats {
            config false;
            leaf count {
                type uint32;
                description " ";
            }
            leaf lastcount {
                type uint32;
                description " ";
            }
            leaf ldelay {
                type uint32;
                description " ";
            }
            leaf drop_next {
                type uint32;
                description " ";
            }
            leaf maxpacket {
                type uint32;
                description " ";
            }
            leaf ecn_mark {
                type uint32;
                description " ";
            }
            leaf drop_overlimit {
                type uint32;
                description " ";
            }
        }
        container fq_codel-stats {
            config false;
            leaf new_flow_count {
                type uint32;
                description " ";
            }
            leaf new_flows_len {
                type uint32;
                description " ";
            }
            leaf old_flows_len {
                type uint32;
                description " ";
            }
        }
    }

    container qdiscs {
        description "Container for all qdisc configurations.";
        list qdisc {
            ipr2cgen:cmd-start;
            ipr2cgen:cmd-add "tc qdisc add";
            ipr2cgen:cmd-delete "tc qdisc del";
            ipr2cgen:cmd-update "tc qdisc replace";
            ipr2cgen:oper-cmd "tc qdisc list";
            ipr2cgen:oper-stop-if '{"kind": ["ingress", "clsact", "noqueue", "mq"]}';
            ipr2cgen:include-all-on-update;
            key "dev parent netns";
            description "List of qdisc configurations.";

            leaf dev {
                type iplink:link-ref;
                description "Name of device 'interface' the qdisc is attached to.";
            }
            leaf parent {
                ipr2cgen:oper-default-val "root";
                type parent-id;
                description "[parent_id 'e.g 8001:1' | root ] Location of the qdisc in the traffic control hierarchy. ";
            }
            leaf netns {
                ipr2cgen:not-cmd-arg;
                onmcli:key-default-val "1";
                ipr2cgen:oper-default-val "1";
                type union {
                    type ipnetns:netns-ref;
                    type enumeration {
                        enum "1";
                    }
                }
                default "1";
                description "network namespace name";
            }
            leaf handle {
                type string {
                    pattern '[0-9a-fA-F]+:';
                }
                description "qdisc handle";
            }
            container estimator {
                ipr2cgen:add-static-arg "estimator";
                description "Configuration for traffic rate estimation.";
                leaf interval {
                    type uint32;
                    description "Time interval in milliseconds for rate estimation.";
                }
                leaf ewma-log {
                    type uint8;
                    description "Exponential Weighted Moving Average (EWMA) log.
                    Represents the weight given to older observations in the moving average.";
                }
            }
            container stab {
                ipr2cgen:add-static-arg "stab";
                description "Configuration for packet size stabilization.";
                leaf mtu {
                    type uint32;
                    description "Maximum Transmission Unit (MTU) for the stab feature.
                    Helps in defining the largest packet size that can be handled.";
                }
                leaf tsize {
                    type uint32;
                    description "Table size for the hash table managing packet sizes.
                    Affects the granularity of the stabilization.";
                }
            }
            leaf qdisc-kind {
                ipr2cgen:value-only;
                ipr2cgen:oper-arg-name "kind";
                type qdisc-kind;

                // ann: don't use leaf name "qdisc-kind" in iproute2 command, only take the value.
                mandatory true;
                description "The kind of qdisc to apply.";
            }
            container fifo-options {
                ipr2cgen:oper-stop-if '{"kind": ["choke", "codel", "fq_codel", "ingress", "clsact",
                                      "tbf", "htb", "hhf", "fq", "fq_pie", "pie", "gred", "mqprio", 
                                      "pfifo-fast", "multiq", "netem", "red", "sfq", "sfb", "ATM", 
                                      "cbq", "drr", "dsmark", "ets", "hfsc", "prio", "qfq"]}';
                ipr2cgen:oper-sub-jobj "options";
                when "(../qdisc-kind = 'pfifo') or (../qdisc-kind = 'bfifo')";
                description "pfifo/bfifo related settings";
                leaf limit {
                    type uint32;
                    description "Maximum queue size. Specified in bytes for bfifo, in
                    packets for pfifo. For pfifo, defaults to the interface
                    txqueuelen, as specified with ifconfig(8) or ip(8).  The
                    range for this parameter is [0, UINT32_MAX].

                    For bfifo, it defaults to the txqueuelen multiplied by the
                    interface MTU.  The range for this parameter is [0,
                    UINT32_MAX] bytes.

                    Note: The link layer header was considered when counting
                    packets length.";
                }
            }
            container codel-options{
                ipr2cgen:oper-stop-if '{"kind": ["choke", "ingress", "clsact", "tbf", "htb", 
                                      "hhf", "fq", "fq_pie", "pie", "gred", "mqprio", "pfifo_fast", 
                                      "bfifo", "pfifo", "multiq", "netem", "red", "sfq", "sfb", 
                                      "ATM", "cbq", "drr", "dsmark", "ets", "hfsc", "prio", "qfq"]}';
                ipr2cgen:oper-sub-jobj "options";
                when "(../qdisc-kind = 'codel') or (../qdisc-kind = 'fq_codel')";
                description "CoDel/fq_CoDel related settings";
                leaf limit {
                    type uint32;
                    default 1000;
                    description "hard limit on the real queue size. When this limit is reached,
                    incoming packets are dropped. If the value is lowered, packets
                    are dropped so that the new limit is met. Default is 1000
                    packets.";
                }
                leaf interval {
                    type uint32;
                    default 99999;
                    description
                        "is used to ensure that the measured minimum delay does not become
                        too stale. The minimum delay must be experienced in the last
                        epoch of length interval.  It should be set on the order of the
                        worst-case RTT through the bottleneck to give endpoints
                        sufficient time to react. Default value is 100ms.";
                }
                leaf memory_limit {
                    when "../../qdisc-kind = 'fq_codel'";
                    type uint32;
                    default 33554432;
                    description
                        "sets a limit on the total number of bytes that can be queued in
                        this FQ-CoDel instance. The lower of the packet limit of the
                        limit parameter and the memory limit will be enforced. Default is
                        32 MB.";
                }
                leaf target {
                    type string; // TODO to be changed
                    description "is the acceptable minimum standing/persistent queue delay. This
                    minimum delay is identified by tracking the local minimum queue
                    delay that packets experience.  Default and recommended value is
                    5ms.";
                    default "5ms";
                }
                leaf flows{
                    when "../../qdisc-kind = 'fq_codel'";
                    type uint16;
                    default 1024;
                    description
                        "is the number of flows into which the incoming packets are
                        classified. Due to the stochastic nature of hashing, multiple
                        flows may end up being hashed into the same slot. Newer flows
                        have priority over older ones. This parameter can be set only at
                        load time since memory has to be allocated for the hash table.
                        Default value is 1024.";
                }
                leaf quantum {
                    when "../../qdisc-kind = 'fq_codel'";
                    type uint32;
                    default 1514;
                    description
                        "is the number of bytes used as 'deficit' in the fair queuing
                        algorithm. Default is set to 1514 bytes which corresponds to the
                        Ethernet MTU plus the hardware header length of 14 bytes.";
                }
                leaf ecn-opt{
                    ipr2cgen:value-only;
                    ipr2cgen:oper-arg-name "ecn";
                    ipr2cgen:oper-value-map '{"true":"ecn", "false":"noecn"}';
                    type enumeration {
                        enum "ecn";
                        enum "noecn";
                    }
                    default "noecn";
                    description
                        "can be used to mark packets instead of dropping them. If ecn has
                        been enabled, noecn can be used to turn it off and vice-a-versa.
                        By default, ecn is turned off.";

                }
                leaf drop_batch {
                    when "../../qdisc-kind = 'fq_codel'";
                    type uint16;
                    default 64;
                    description
                        "sets the maximum number of packets to drop when limit or
                        memory_limit is exceeded. Default value is 64.";
                }
                leaf ce_threshold {
                    type uint16; // TODO to be changed
                    description "configured in micro seconds";
                }
                uses codel-stats;
            }
            container tbf-options {
                ipr2cgen:oper-stop-if '{"kind": ["choke", "codel", "fq_codel", "ingress", "clsact", 
                                      "htb", "hhf", "fq", "fq_pie", "pie", "gred", "mqprio", "pfifo_fast", 
                                      "bfifo", "pfifo", "multiq", "netem", "red", "sfq", "sfb", "ATM", 
                                      "cbq", "drr", "dsmark", "ets", "hfsc", "prio", "qfq"]}';
                ipr2cgen:oper-sub-jobj "options";
                when "../qdisc-kind = 'tbf'";
                must "./rate and ./burst" {
                    error-message "rate and burst are required for tbf qdisc";
                }
                must "./limit or ./latency" {
                    error-message "either \"limit\" or \"latency\" is required. for tbf qdisc";
                }
                description
                    "The Token Bucket Filter is a classful queueing discipline
                    available for traffic control with the tc(8) command.

                    TBF is a pure shaper and never schedules traffic. It is non-work-
                    conserving and may throttle itself, although packets are
                    available, to ensure that the configured rate is not exceeded.
                    It is able to shape up to 1mbit/s of normal traffic with ideal
                    minimal burstiness, sending out data exactly at the configured
                    rates.

                    Much higher rates are possible but at the cost of losing the
                    minimal burstiness. In that case, data is on average dequeued at
                    the configured rate but may be sent much faster at millisecond
                    timescales. Because of further queues living in network adaptors,
                    this is often not a problem.";
                leaf rate {
                    type string;
                    description
                        "The speed knob. See remarks above about limits! See tc(8)
                        for units. ese parameters accept a floating
                        point number, possibly followed by either a unit (both SI
                        and IEC units supported), or a float followed by a '%'
                        character to specify the rate as a percentage of the
                        device's speed (e.g. 5%, 99.5%). Warning: specifying the
                        rate as a percentage means a fraction of the current
                        speed; if the speed changes, the value will not be
                        recalculated.

                        bit or a bare number
                        Bits per second

                        kbit   Kilobits per second
                        mbit   Megabits per second
                        gbit   Gigabits per second
                        tbit   Terabits per second
                        bps    Bytes per second
                        kbps   Kilobytes per second
                        mbps   Megabytes per second
                        gbps   Gigabytes per second
                        tbps   Terabytes per second";
                }
                leaf burst {
                    type string; // TODO to be changed
                    description
                        "Size of the bucket, in
                        bytes. This is the maximum amount of bytes that tokens can
                        be available for instantaneously.  In general, larger
                        shaping rates require a larger buffer. For 10mbit/s on
                        Intel, you need at least 10kbyte buffer if you want to
                        reach your configured rate!

                        If your buffer is too small, packets may be dropped
                        because more tokens arrive per timer tick than fit in your
                        bucket.  The minimum buffer size can be calculated by
                        dividing the rate by HZ.

                        Token usage calculations are performed using a table which
                        by default has a resolution of 8 packets.  This resolution
                        can be changed by specifying the cell size with the burst.
                        For example, to specify a 6000 byte buffer with a 16 byte
                        cell size, set a burst of 6000/16. You will probably never
                        have to set this. Must be an integral power of 2.";
                }
                choice queue-limit {
                    case byte-limit{
                        leaf limit {
                            type uint32;
                            description
                                "Limit the number of bytes that can be queued waiting
                                for tokens to become available";
                        }
                    }
                    case pkt-latency {
                        leaf latency {
                            ipr2cgen:oper-arg-name "lat";
                            type uint32;
                            description
                                "specifies the maximum amount of time a packet can
                                sit in the TBF.";
                        }
                    }

                }
                leaf mpu {
                    type uint16;
                    default 0;
                    description
                        "A zero-sized packet does not use zero bandwidth. For
                        ethernet, no packet uses less than 64 bytes. The Minimum
                        Packet Unit determines the minimal token usage (specified
                        in bytes) for a packet. Defaults to zero.";
                }
                leaf peakrate {
                    type uint32;
                    description
                        "Maximum depletion rate of the bucket. The peakrate does
                        not need to be set, it is only necessary if perfect
                        millisecond timescale shaping is required.";
                }
                leaf mtu {
                    type uint16;
                    description
                        " Specifies the size of the peakrate bucket. For perfect
                        accuracy, should be set to the MTU of the interface.  If a
                        peakrate is needed, but some burstiness is acceptable,
                        this size can be raised. A 3000 byte minburst allows
                        around 3mbit/s of peakrate, given 1000 byte packets.";
                }
                leaf linklayer {
                    config false;
                    type string;
                    description "";
                }

            }
            container htb-options {
                ipr2cgen:oper-stop-if '{"kind": ["choke", "codel", "fq_codel", "ingress", 
                                      "clsact", "tbf", "hhf", "fq", "fq_pie", "pie", "gred", 
                                      "mqprio", "pfifo_fast", "bfifo", "pfifo", "multiq", 
                                      "netem", "red", "sfq", "sfb", "ATM", "cbq", "drr", "dsmark", 
                                      "ets", "hfsc", "prio", "qfq"]}';
                ipr2cgen:oper-sub-jobj "options";
                when "../qdisc-kind = 'htb'";
                description
                    "The Token Bucket Filter is a classful queueing discipline
                    available for traffic control with the tc(8) command.

                    TBF is a pure shaper and never schedules traffic. It is non-work-
                    conserving and may throttle itself, although packets are
                    available, to ensure that the configured rate is not exceeded.
                    It is able to shape up to 1mbit/s of normal traffic with ideal
                    minimal burstiness, sending out data exactly at the configured
                    rates.

                    Much higher rates are possible but at the cost of losing the
                    minimal burstiness. In that case, data is on average dequeued at
                    the configured rate but may be sent much faster at millisecond
                    timescales. Because of further queues living in network adaptors,
                    this is often not a problem.";
                leaf default {
                    type string {
                        pattern '(0x)?[0-9a-fA-F]+|\d+';
                    }
                    description
                        "Unclassified traffic gets sent to the class with this
                        minor-id.";
                }
                leaf offload {
                    ipr2cgen:flag;
                    ipr2cgen:oper-value-map '{"true":"on"}';
                    type enumeration {
                        enum "on";
                    }

                }

            }
            uses qdisc-stats;
        }
        list special-qdisc {
            ipr2cgen:cmd-start;
            ipr2cgen:cmd-add "tc qdisc add";
            ipr2cgen:cmd-delete "tc qdisc del";
            ipr2cgen:cmd-update "tc qdisc replace";
            ipr2cgen:include-all-on-update;
            ipr2cgen:oper-cmd "tc qdisc list";
            ipr2cgen:oper-stop-if '{"kind": ["choke", "codel", "fq_codel", "tbf", "htb", "hhf", 
                                  "fq", "fq_pie", "pie", "gred", "mqprio", "pfifo_fast", "bfifo", 
                                  "pfifo", "multiq", "netem", "red", "sfq", "sfb", "ATM", "cbq", 
                                  "drr", "dsmark", "ets", "hfsc", "prio", "qfq", "noqueue", "mq"]}';
            key "dev qdisc-kind netns";
            unique "dev";
            description "List of qdisc configurations.";
            leaf dev {
                type iplink:link-ref;
                description "Name of device 'interface' the qdisc is attached to.";
            }
            leaf qdisc-kind {
                ipr2cgen:value-only;
                ipr2cgen:add_leaf_at_end;
                ipr2cgen:oper-arg-name "kind";
                mandatory true;
                type enumeration {
                    enum "ingress" {
                        description "a special qdisc as it applies to incoming traffic on an interface,
                        allowing for it to be filtered and policed.";
                    }
                    enum "clsact" {
                        description "a special qdisc as it applies to incoming and outgoing traffic on an interface,
                        allowing for it to be filtered and policed.";
                    }
                }
            }
            leaf netns {
                ipr2cgen:not-cmd-arg;
                onmcli:key-default-val "1";
                ipr2cgen:oper-default-val "1";
                type union {
                    type ipnetns:netns-ref;
                    type enumeration {
                        enum "1";
                    }
                }
                default "1";
                description "network namespace name";
            }
            leaf ingress_block {
                type uint32;
                description "Ingress tc shared block ID";
            }
            leaf egress_block {
                when "../qdisc-kind='clsact'";
                type uint32;
                description "egress tc shared block ID";
            }
            uses qdisc-stats;
        }
    }
    container classes {
        list class {
            ipr2cgen:cmd-start;
            ipr2cgen:cmd-add "tc class add";
            ipr2cgen:cmd-delete "tc class del";
            ipr2cgen:cmd-update "tc class change";
            ipr2cgen:include-all-on-update;
            ipr2cgen:oper-dump-tc-classes;
            key "dev parent classid netns";
            leaf dev {
                type iplink:link-ref;
                description
                    "link to attach this class to";
            }
            leaf parent {
                type union {
                    type leafref {
                        path '/qdisc:qdiscs/qdisc:qdisc/qdisc:handle';
                    }
                    type leafref {
                        path '/qdisc:classes/qdisc:class/qdisc:classid';
                    }
                    type enumeration {
                        enum "root";
                    }
                }

                description
                    "class's parent, can be qdisc hanlde or other classid";
            }
            leaf classid {
                ipr2cgen:oper-arg-name "handle";
                type string {
                    pattern '[0-9a-fA-F]+:[0-9a-fA-F]+';
                }
                description
                    "";
            }
            leaf netns {
                ipr2cgen:not-cmd-arg;
                onmcli:key-default-val "1";
                ipr2cgen:oper-default-val "1";
                type union {
                    type ipnetns:netns-ref;
                    type enumeration {
                        enum "1";
                    }
                }
                default "1";
                description "network namespace name";
            }
            choice qdisc-options {
                mandatory true;
                container htb {
                    ipr2cgen:oper-stop-if '{"class": ["cbq"]}';
                    ipr2cgen:add-static-arg "htb";
                    leaf prio {
                        type uint32;
                        default 0;
                        description
                            "class priority";
                    }
                    leaf rate {
                        ipr2cgen:oper-change-value-format '{"byte": "bit-units"}';
                        type bit-units;
                        description
                            "Maximum rate this class and all its children are
                            guaranteed. Mandatory. example 1kbit,3mbit etc ";
                    }
                    leaf ceil {
                        ipr2cgen:oper-change-value-format '{"byte": "bit-units"}';
                        type bit-units;
                        description
                            "Maximum rate at which a class can send, if its parent has
                            bandwidth to spare.  Defaults to the configured rate,
                            which implies no borrowing";
                    }
                    leaf burst {
                        type uint64;
                        description
                            "Amount of bytes that can be burst at ceil speed, in excess
                            of the configured rate.  Should be at least as high as the
                            highest burst of all children.";
                    }
                    leaf cburst {
                        type uint64;
                        description
                            " Amount of bytes that can be burst at 'infinite' speed, in
                            other words, as fast as the interface can transmit them.
                            For perfect evening out, should be equal to at most one
                            average packet. Should be at least as high as the highest
                            cburst of all children.";
                    }
                    leaf quantum {
                        type uint32;
                        description
                            "Number of bytes to serve from this class before the
                            scheduler moves to the next class.  Default value is rate
                            divided by the qdisc r2q parameter.  If specified, r2q is
                            ignored.";
                    }

                }
                container cbq {
                    ipr2cgen:oper-stop-if '{"class": ["htb"]}';
                    ipr2cgen:add-static-arg "cbq";
                    leaf weight {
                        type bit-units;
                        description
                            "When dequeuing to the interface, classes are tried for traffic in a round-robin fashion.
                            Classes with a higher configured qdisc will generally have more traffic to offer during
                            each round, so it makes sense to allow it to dequeue more traffic. All weights under
                            a class are normalized, so only the ratios matter. Defaults to the configured rate,
                            unless the priority of this class is maximal, in which case it is set to 1.";
                    }
                    leaf allot {
                        type uint32;
                        mandatory true;
                        description
                            "Allot specifies how many bytes a qdisc can dequeue during each round of the process.
                            This parameter is weighted using the renormalized class weight described above.
                            Silently capped at a minimum of 3/2 avpkt. Mandatory.";
                    }
                    leaf prio {
                        type uint32;
                        mandatory true;
                        description
                            "In the round-robin process,
                            classes with the lowest priority field are tried for packets first.";
                    }
                    leaf avpkt {
                        type uint32;
                        description
                            "Average size of a packet, measured in bytes. Needed for calculating maxidle,
                            which is derived from maxburst, which is specified in packets.";
                    }
                    leaf rate {
                        type bit-units;
                        description
                            "Desired rate of traffic leaving this qdisc - this is the 'speed knob'!";
                    }
                    leaf bandwidth {
                        type bit-units;
                        description
                            "This is different from the bandwidth specified when creating a CBQ disc! Only
                            used to determine maxidle and offtime, which are only calculated when specifying
                            maxburst or minburst. Mandatory if specifying maxburst or minburst.";
                    }
                    leaf minburst {
                        type uint16;
                        description
                            "CBQ needs to throttle in case of overlimit. The ideal solution is to do so for
                            exactly the calculated idle time, and pass 1 packet. However, Unix kernels generally
                            have a hard time scheduling events shorter than 10ms, so it is better to throttle for
                            a longer period, and then pass minburst packets in one go, and then sleep minburst times longer.
                            The time to wait is called the offtime. Higher values of minburst lead to more accurate shaping
                            in the long term, but to bigger bursts at millisecond timescales. Optional.";
                    }
                    leaf maxburst {
                        type uint16;
                        description
                            "This number of packets is used to calculate maxidle so that when avgidle is at maxidle,
                            this number of average packets can be burst before avgidle drops to 0. Set it higher to
                            be more tolerant of bursts. You can't set maxidle directly, only via this parameter.";
                    }
                    leaf minidle {
                        type uint32;
                        description
                            "If avgidle is below 0, we are overlimits and need to wait until avgidle will be big
                            enough to send one packet.To prevent a sudden burst from shutting down the link for a
                            prolonged period of time, avgidle is reset to minidle if it gets too low.

                            Minidle is specified in negative microseconds, so 10 means that avgidle is capped at -10us.";
                    }
                    leaf mpu {
                        type uint32;
                        description
                            "Minimum packet size - needed because even a zero size packet is padded to 64 bytes on
                            ethernet, and so takes a certain time to transmit. CBQ needs to know this to accurately
                            calculate the idle time.";
                    }
                }
            }
        }
    }

}

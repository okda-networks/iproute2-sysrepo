module iproute2-ip-nexthop {
    yang-version 1.1;
    namespace "urn:okda:iproute2:ip:nexthop";
    prefix "ipnh";

    import ietf-inet-types { prefix inet; }
    import iproute2-ip-link { prefix iplink; }
    import okda-onmcli-extensions{ prefix onmcli; }
    import iproute2-cmdgen-extensions { prefix ipr2cgen; }
    import iproute2-ip-netns { prefix ipnetns; }

    organization
        "Okda Networks";

    contact
        "Author: Ali Aqrabawi
        <aaqrabaw@okdanetworks.com>";

    description
        "This module contain the iproute2 'ip nexthop' configurations ,
        this is module contains all IP-NEXTHOP(8) related configs,
        refer to https://manpages.debian.org/experimental/iproute2/ip-nexthop.8.en.html";

    revision "2024-02-13" {
        description "Revision 1";
        reference
            "YANG model for iproute2 ip nexthop case.";
    }

    container nexthops{

        description
            "iproute2 nexthops configurations";
        list nexthop{
            ipr2cgen:cmd-start;
            ipr2cgen:cmd-add "ip nexthop add";
            ipr2cgen:cmd-update "ip nexthop replace";
            ipr2cgen:cmd-delete "ip nexthop del";
            ipr2cgen:include-all-on-update;
            ipr2cgen:oper-cmd "ip nexthop show";
            key "id netns";
            description
                "nexthop configuraton";
            leaf id{
                ipr2cgen:value-only-on-update;
                description "nexthop id";
                type uint32;
            }
            leaf netns {
                ipr2cgen:not-cmd-arg;
                onmcli:key-default-val "1";
                ipr2cgen:oper-default-val "1";
                type union {
                    type ipnetns:netns-ref;
                    type enumeration {
                        enum "1";
                    }
                }
                default "1";
                description "network namespace name";
            }
            leaf dev {
                description "Specifies the network interface associated with the nexthop.";
                type iplink:l3-links-ref;
            }
            choice via {
                description "nexthop ip address";
                container ipv4 {
                    description "ipv4 nexthop";
                    leaf address {
                        ipr2cgen:arg-name "via";
                        ipr2cgen:oper-arg-name "gateway";
                        description "ipv4 nexthop address";
                        type inet:ipv4-address;
                    }
                }
                container ipv6 {
                    description "ipv6 nexthop";
                    ipr2cgen:arg-name "via";
                    ipr2cgen:oper-arg-name "gateway";
                    leaf address {
                        description "ipv6 nexthop address";
                        type inet:ipv6-address;
                    }
                }

            }
            leaf blackhole {
                ipr2cgen:flag;
                ipr2cgen:oper-ck-argname-presence "true";
                description "specify if this is blackhole nexthop, which discards all traffic sent to it.";
                type boolean;
                when "not(../dev) and not(../ipv6) and not(../ipv4)";
            }
            leaf onlink {
                ipr2cgen:flag;
                type boolean;
                description "Indicates that the nexthop is directly reachable on the link.";
            }
            choice encap {
                container mpls {
                    leaf label-stack {
                        type string{
                            pattern '(\d+)(/\d+)*';
                        }
                        description "mpls label stack with labels separated by /, example 200/300";

                    }
                    leaf ttl {
                        type uint8 {
                            range "0..255";
                        }
                        description "TTL to use for MPLS header or 0 to inherit from IP header";
                    }
                }
            }
            container group {
                description "create a nexthop group. Group specification is id with an optional weight";
                list nh {
                    key "id weight";
                    ipr2cgen:group-list-with-separator "/";
                    ipr2cgen:group-leafs-values-separator ",";
                    ipr2cgen:arg-name "group";
                    ipr2cgen:oper-arg-name "group";
                    leaf id{
                        type leafref {
                            path "/ipnh:nexthops/nexthop/id";

                        }
                        must ". != ../../../id" {
                            error-message "Cannot reference the current nexthop ID, you can use other nexthops ids";
                        }
                        description "specify the nexthop id you want to add to this next";
                    }
                    leaf weight {
                        description "nexthop weight for this member";
                        type uint16;
                    }
                }
                leaf type {
                    default "mpath";
                    type enumeration {
                        enum "mpath";
                        enum "resilient";
                    }
                    description "specifying the nexthop group type";

                }
                leaf resilient-buckets {
                    when "../type='resilient'";
                    type uint16;
                    description "Number of nexthop buckets. Cannot be changed for an existing group";
                }
                leaf resilient-idle-timer {
                    when "../type='resilient'";
                    type uint16;
                    description "Time in seconds in which a nexthop bucket does not see traffic
                    and is therefore considered idle. Default is 120 seconds";
                }
                leaf resilient-unbalanced_timer {
                    when "../type='resilient'";
                    type uint32;
                    description "Time in seconds in which a nexthop group is unbalanced and is therefore considered
                    unbalanced. The kernel will try to rebalance unbalanced groups,
                    which might result in someflows being reset. A value of 0 means that no rebalancing
                    will take place. Default is 0 seconds";
                }
            }
            leaf fdb {
                ipr2cgen:flag;
                ipr2cgen:oper-ck-argname-presence "true";
                type boolean;
                description "nexthop and nexthop groups for use with layer-2 fdb entries.
                A fdb nexthop group can only have fdb nexthops. Example: Used to represent a vxlan remote
                vtep ip. layer-2 vxlan fdb entry pointing to an ecmp nexthop group containing multiple
                remote vtep ips.";
            }
        }

    }
}

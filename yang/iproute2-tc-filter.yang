module iproute2-tc-filter {
    yang-version 1.1;
    namespace "urn:okda:iproute2:tc:filter";
    prefix "filter";

    import ietf-inet-types { prefix inet; }
    import okda-onmcli-extensions{ prefix onmcli; }
    import iproute2-cmdgen-extensions { prefix ipr2cgen; }
    import iproute2-ip-link { prefix iplink; }
    import iproute2-ip-netns { prefix ipnetns; }
    import iproute2-tc-qdisc { prefix qdisc; }

    organization "Okda Networks";
    contact
        "Author: Amjad Daraiseh
        <adaraiseh@okdanetworks.com>";

    description
        "This module contain the iproute2 'tc filter' configurations.
        This is module contains tc - show / manipulate 'filters' settings.
        refer to https://manpages.debian.org/bookworm/iproute2/tc.8.en.html";

    revision "2024-02-18" {
        description "Initial version.";
    }

    grouping filter-state {
        container state {
            config false;
            leaf installed {
                type uint64;
                description "Time in seconds passed since the filter was installed.";
            }
            leaf last_used {
                type uint64;
                description "Time in seconds passed since the filter was last used.";
            }
            leaf first_used {
                type uint64;
                description "Time in seconds passed since the filter was first used.";
            }
            leaf expires {
                type uint64;
                description "Time in seconds until filter expires.";
            }
            container stats {
                description "Contains 64-bit counters for various network statistics.
                Providing detailed information on the traffic handled by the filter.";
                leaf bytes {
                    type uint64;
                    description "Total number of bytes received by the filter.";
                }
                leaf packets {
                    type uint64;
                    description "Total number of packets received by the filter.";
                }
                leaf drops {
                    type uint64;
                    description "Number of packets dropped by the filter.";
                }
                leaf overlimits {
                    type uint64;
                    description " The number of times the filter has encountered a situation where it exceeded 
                    its configured limits (e.g., rate limits).";
                }
                leaf requeues {
                    type uint64;
                    description "The number of packets that have been requeued by the filter.";
                }
                leaf backlog {
                    type uint64;
                    description "TThe current amount of data (in bytes) that is waiting in the queue for this filter.";
                }
                leaf qlen {
                    type uint64;
                    description "filter queue length.";
                }
            }
        }
    }
    grouping filter-common {
        leaf netns {
            ipr2cgen:not-cmd-arg;
            onmcli:key-default-val "1";
            ipr2cgen:oper-default-val "1";
            type union {
                type ipnetns:netns-ref;
                type enumeration {
                    enum "1";
                }
            }
            default "1";
            description "network namespace name";
        }
    }
    grouping filter-result {
        leaf classid {
            type leafref {
                path '/qdisc:classes/qdisc:class/qdisc:classid';
            }
            description
                "[also called flowid] pecify a class to pass matching packets on to.  CLASSID
                is in the form X:Y, while X and Y are interpreted as
                numbers in hexadecimal format.";
        }

        container actions {
            ipr2cgen:oper-sub-jobj "actions";
            leaf gact {
                ipr2cgen:arg-name "action";
                ipr2cgen:oper-sub-jobj "control_action";
                ipr2cgen:oper-arg-name "type";
                type enumeration {
                    enum "pass";
                    enum "drop";
                    enum "reclassify";
                    enum "continue";
                    enum "pipe";
                }
                description
                    "specify action";
            }
            container nat {
                leaf direction {
                    ipr2cgen:arg-name "action nat ";
                    must "../old_ip and ../new_ip"{
                        error-message "direction, old_ip and new_ip are mandatory for nat action.";
                    }
                    type enumeration {
                        enum "ingress";
                        enum "egress";
                    }
                    description "NAT direction";
                }
                leaf old_ip {
                    ipr2cgen:value-only;
                    ipr2cgen:oper-arg-name "old_addr";
                    must "../direction and ../new_ip"{
                        error-message "direction, old_ip and new_ip are mandatory for nat action.";
                    }
                    type union {
                        type inet:ip-address;
                        type inet:ip-prefix;
                    }
                    description "original ip";
                }
                leaf new_ip {
                    ipr2cgen:value-only;
                    ipr2cgen:oper-arg-name "new_addr";
                    must "../direction and ../old_ip"{
                        error-message "direction, old_ip and new_ip are mandatory for nat action.";
                    }
                    type inet:ip-address;
                    description "natted ip";
                }

            }
        }
    }
    grouping filter-rule{
        list rule{
            ipr2cgen:cmd-start;
            ipr2cgen:cmd-add "tc filter add";
            ipr2cgen:cmd-delete "tc filter del";
            ipr2cgen:cmd-update "tc filter add";
            ipr2cgen:replace-on-update;
            ipr2cgen:include_parent_leafs;
            ipr2cgen:include-all-on-update;
            key "pref";
            leaf pref {
                type uint32;
                description "the preference value";
            }
            leaf protocol {
                type enumeration {
                    enum "ip";
                }
                description "EthType protocol.";
                default "ip";
            }
            leaf handle {
                type string {
                    pattern '0x[0-9a-fA-F]+|\d+';
                }
                description "The filter ID.";
                default "0x1";
            }
            leaf prio {
                type uint8;
                description "The priority.";
            }
            uses filter-state;
            choice filter {
                //ipr2cgen:oper-arg-name "kind";
                container flower {
                    ipr2cgen:add-static-arg "flower";
                    ipr2cgen:oper-stop-if '{"kind": ["u32"]}';
                    container match {
                        leaf indev {
                            type iplink:link-ref;
                            description
                                "Match on incoming interface name. Obviously this makes
                                sense only for forwarded flows.  ifname is the name of an
                                interface which must exist at the time of tc invocation.";
                        }
                        leaf skip_sw {
                            ipr2cgen:flag;
                            type boolean;
                            description
                                "Do not process filter by software. If hardware has no
                                offload support for this filter, or TC offload is not
                                enabled for the interface, operation will fail.";
                        }
                        leaf skip_hw {
                            ipr2cgen:flag;
                            type boolean;
                            description
                                "Do not process filter by hardware.";
                        }
                        leaf dst_mac {
                            type string; // TODO: add pattern
                            description
                                "Match on destination MAC address.  A mask may be
                                optionally provided to limit the bits of the address which
                                are matched. A mask is provided by following the address
                                with a slash and then the mask. It may be provided in
                                LLADDR format, in which case it is a bitwise mask, or as a
                                number of high bits to match. If the mask is missing then
                                a match on all bits is assumed.";
                        }
                        leaf src_mac {
                            type string; // TODO: add pattern
                            description
                                "Match on source MAC address.  A mask may be
                                optionally provided to limit the bits of the address which
                                are matched. A mask is provided by following the address
                                with a slash and then the mask. It may be provided in
                                LLADDR format, in which case it is a bitwise mask, or as a
                                number of high bits to match. If the mask is missing then
                                a match on all bits is assumed.";
                        }
                        leaf vlan_id {
                            type uint32;
                            description
                                " Match on vlan tag id.  VID is an unsigned 12bit value in
                                decimal format.";
                        }
                        leaf ip_proto {
                            type union {
                                type string{
                                    pattern '0x[0-9a-fA-F]+|\d+';
                                }
                                type enumeration {
                                    enum "tcp";
                                    enum "udp";
                                    enum "icmp";
                                    enum "icmpv6";
                                }

                            }
                            description
                                "Match on layer four protocol.  IP_PROTO may be tcp, udp,
                                sctp, icmp, icmpv6, l2tp or an unsigned 8bit value in
                                hexadecimal format.";
                        }
                        leaf ip_tos {
                            type string{
                                pattern '0x[0-9a-fA-F]+|\d+';
                            }
                            description
                                "Match on ipv4 TOS or ipv6 traffic-class - eight bits in
                                hexadecimal format.  A mask may be optionally provided to
                                limit the bits which are matched. A mask is provided by
                                following the value with a slash and then the mask. If the
                                mask is missing then a match on all bits is assumed.";
                        }
                        leaf ip_ttl {
                            type string {
                                pattern '0x[0-9a-fA-F]+|\d+';
                            }
                            description
                                "Match on ipv4 TTL or ipv6 hop-limit  - eight bits value in
                                decimal or hexadecimal format.  A mask may be optionally
                                provided to limit the bits which are matched. Same logic
                                is used for the mask as with matching on ip_tos.";
                        }
                        leaf dst_ip {
                            type union {
                                type inet:ip-address;
                                type inet:ip-prefix;
                            }

                            description
                                "Match on destination IP address.  PREFIX must be
                                a valid IPv4 or IPv6 address, depending on the protocol
                                option to tc filter, optionally followed by a slash and
                                the prefix length.  If the prefix is missing, tc assumes a
                                full-length host match.";
                        }
                        leaf src_ip {
                            type union {
                                type inet:ip-address;
                                type inet:ip-prefix;
                            }

                            description
                                "Match on source IP address.  PREFIX must be
                                a valid IPv4 or IPv6 address, depending on the protocol
                                option to tc filter, optionally followed by a slash and
                                the prefix length.  If the prefix is missing, tc assumes a
                                full-length host match.";
                        }
                        leaf dst_port {
                            when "../ip_proto = 'tcp' or ../ip_proto = 'udp'";
                            type inet:port-number;
                            description
                                "Match on layer 4 protocol  destination port
                                number, with an optional mask. Alternatively, the minimum
                                and maximum values can be specified to match on a range of
                                layer 4 protocol  destination port numbers. Only
                                available for ip_proto values udp, tcp and sctp which have
                                to be specified in beforehand.";
                        }
                        leaf src_port {
                            when "../ip_proto = 'tcp' or ../ip_proto = 'udp'";
                            type inet:port-number;
                            description
                                "Match on layer 4 protocol source port
                                number, with an optional mask. Alternatively, the minimum
                                and maximum values can be specified to match on a range of
                                layer 4 protocol source  port numbers. Only
                                available for ip_proto values udp, tcp and sctp which have
                                to be specified in beforehand..";
                        }
                    }
                    uses filter-result;

                }
                container u32 {
                    ipr2cgen:add-static-arg "u32";
                    ipr2cgen:oper-stop-if '{"kind": ["flower"]}';
                    container match {
                        ipr2cgen:add-static-arg "match";
                        ipr2cgen:oper-sub-jobj "match";
                        container ip {
                            ipr2cgen:add-static-arg "ip";
                            leaf src {
                                type union {
                                    type inet:ip-address;
                                    type inet:ip-prefix;
                                }
                                description
                                    "source ip prefix";

                            }
                            leaf dst {
                                type union {
                                    type inet:ip-address;
                                    type inet:ip-prefix;
                                }
                                description
                                    "destination ip prefix";

                            }
                        }
                        container tcp {
                            ipr2cgen:add-static-arg "tcp";
                            leaf sport {
                                type inet:port-number;
                                description
                                    "source port number";
                            }
                            leaf dport {
                                type inet:port-number;
                                description
                                    "destination port number";
                            }
                        }
                        container udp {
                            ipr2cgen:add-static-arg "udp";
                            leaf sport {
                                type inet:port-number;
                                description
                                    "source port number";
                            }
                            leaf dport {
                                type inet:port-number;
                                description
                                    "destination port number";
                            }
                        }

                    }
                    uses filter-result;

                }
            }

        }
    }

    container tc-filters {
        description "Container for all tc filter configurations.";
        list qdisc-filter {
            ipr2cgen:oper-dump-tc-filters "not-supported";
            key "dev parent netns";
            description "filter that is applied to qdisc";
            leaf dev {
                type leafref {
                    path '/qdisc:qdiscs/qdisc:qdisc/qdisc:dev';
                }
                description "Name of device 'link' where the qdisc is attached to, the link must have qdisc attached to it.";
                mandatory true;
            }
            leaf parent {
                type leafref {
                    path '/qdisc:qdiscs/qdisc:qdisc/qdisc:handle';
                }
                description "qdisc handler where is filter is attached to.";
                mandatory true;
            }
            uses filter-common;
            uses filter-rule;

        }
        list dev-filter {
            ipr2cgen:oper-dump-tc-filters "dev-filter";
            description "A list of filters.";
            key "dev direction netns";
            leaf dev {
                type leafref {
                    path '/qdisc:qdiscs/qdisc:special-qdisc/qdisc:dev';
                }
                description "Name of device 'interface' the filter is attached to.";
                mandatory true;
            }
            leaf direction {
                ipr2cgen:value-only;
                type enumeration {
                    enum "ingress";
                    enum "egress";
                }
            }

            uses filter-common;
            uses filter-rule;
        }
        list shared-block-filter {
            ipr2cgen:oper-dump-tc-filters "shared-block-filter";
            key "block netns";
            leaf block {
                type union{
                    type leafref {
                        path '/qdisc:qdiscs/qdisc:special-qdisc/qdisc:ingress_block';
                    }
                    type leafref {
                        path '/qdisc:qdiscs/qdisc:special-qdisc/qdisc:egress_block';
                    }
                }
                description
                    "shared block id";
            }
            uses filter-common;
            uses filter-rule;
        }
    }
}

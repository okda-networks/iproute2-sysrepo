module iproute2-cmdgen-extensions {
    yang-version 1.1;
    namespace "urn:okda:iproute2:cmdgen:extensions";
    prefix "ipr2cgen";

    organization
        "Okda networks";

    contact
        "Author: Ali Aqrabawi
        <aaqrabaw@okdanetworks.com>";

    description
        "This module provide extensions to parse yang data to ip route cmd";

    extension cmd-start {
        description
            "define at which node a new cmd start, typically used in the first list in the schema, example
            ir2cmd:cmd-start";

    }

    extension cmd-add {
        description
            "define the add cmd prefix , typically used in the first container, example
            ir2cmd:cmd-add \"ip link add\" ";
        argument "cmd";

    }
    extension cmd-delete {
        description
            "define the delete cmd prefix , typically used in the first container, example
            ir2cmd:cmd-add \"ip link delete\" ";
        argument "cmd";

    }
    extension cmd-update {
        description
            "define the update cmd prefix , typically used in the first container, example
            ir2cmd:cmd-add \"ip link set\" ";
        argument "cmd";

    }

    extension arg-name {
        description
            "iproute2 cmd generator will use the leaf name as argname when generating the cmd, to override this use
            arg-name extension";
        argument "arg-name";
    }

    extension oper-arg-name {
        description
            "iproute2 operational data extraction will use the leaf name for data lookup in iproute2 json outputs.
            to override this use oper-arg-name extension";
        argument "arg-name";
    }

    extension oper-value-map {
       description "used to map iproute2 operational data values to yang module vales";
       argument "value_map";
    }

    extension oper-flag-map {
       description "used to map iproute2 operational data values to yang module values";
       argument "flag_map";
    }

    extension oper-change-value-format {
        description "Instructs to convert iproute2 json output value from to a desired format.
        it takes a json key pair where the key_name is the orignal format and the key value is the desired format.
        example to convert bytes to packet rate use {\"byte\": \"bit-units\"}";
        argument "conversion_key";
    }

    extension oper-combine-values {
       description "used to combine iproute2 operational json data keys in one leaf, comined 
       json key names are expressed in json list format, the list key should be the combination 
       separator and the values are the iproute2 json output key names to have their values combined.
       This extension json list should be defined as follows:
       {'separator':'separator_value', 'values': ['key_of_value1', 'key_of_value2' , 'key_of_valueN']}
       
       Example use case : {\"separator\" : \"/\" , \"values\" : [\"local\" , \"prefixlen\"]}
       This will instruct the code to lookup 'local' key value and 'prefixlen' key value from iproute2
       show command json outputs and combine them togther using the separator value defined the extension
       list key '/'";
       argument "combine_list";
    }

    extension oper-ck-argname-presence {
       description "used to instruct operational data to lookup the argname only in iproute2 operational data 
                    outputs, if found the value is defined by the extension argument this is typically used 
                    in leafs where ipr2 displays the flag as json key and key value as null";
       argument "static_value";
    }

    extension oper-default-val {
       description "used to instruct operational data to always set default value for a leaf if not found
       in iproute2 show outputs";
       argument "default_value";
    }

    extension oper-stop-if {
       description "Instructs oper data to stop processing node (and its children) if one of its values matches a value in the 
       extension argument values list, the key and values are expected to be expressed in json array format.
       for example: to stop processing node if the node show command outputs contains \"info_kind\" key with values of \"vlan\" or \"vti\"
       then the used argument should be set tp : {\"info_kind\": [\"vlan\", \"vti\"]}";
       argument "stop_key_and_values";
    }

    extension oper-sub-jobj {
       description "Instructs oper data to extract specific json object from the main outputs json data to be used for further data porcessing.
       This helps avoiding leaf names conflicts in cases the leaf name matches two objects in the main json data updating the json object to 
       a subset of the main object resolves this conflict, this is typically used inside containers to narrow down their data json object to 
       subset of the main data object";
       argument "sub_json_object_name";
    }

    extension oper-cmd {
       description "define node which a new show cmd is needed, typically used in the first list in the schema, example
                    ir2cmdgen:oper-cmd \"ip link show type vrf\"";
       argument "show_cmd";
    }

    extension oper-inner-cmd {
        description "define node which a new show cmd is needed, typically used in the first list in the schema, example
        ir2cmdgen:oper-cmd \"ip link show type vrf\"";
        argument "show_cmd";
    }

    extension oper-dump-tc-filters {
        description "A sepcial extension to dump all tc filters configured on the system and load them on tc-filter yang
        module";
        argument "filter_type";
    }

    extension oper-dump-tc-classes {
        description "A sepcial extension to dump all tc classes configured on the system and load them on tc-qdisc yang
        module";
    }

    extension flag {
        description
            "iproute2 cmd generator will use the leaf name only, ususally used for flags where the leaf type will be bool,
            e.g \"ip nexthop add id 100 blackhole\" (blackhole is flag, and it's type is bool in yang)";
    }

    extension value-only{
        description
            "instruct iproute2 to drop the leaf name (key) when generating the cmd, example \"ip link add dummy0 up\"";
    }

    extension value-only-on-update{
        description
            "instruct iproute2 to drop the leaf name (key) when generating the update cmd";
    }
    extension on-update-include{
        description
            "instruct iproute2 to include the leaf(s) specified by arg-name (coma ',' separated) to be included
            on update cmd";
        argument "args-names";
    }
    extension include-all-on-update{
        description
            "instruct iproute2 to get all leafs in sysrepo, compare it with the changed leaf, and apply the diff.
            typically used where iproute2 cmd require a replace for update, example tc filter, and ip nexthop group";
    }
    extension replace-on-update{
        description
            "instruct iproute2 to delete the node and recreate it, example ip rule where no update argument, you have to
            recreate the rule";
    }
    extension include-all-on-delete {
        description
            "instruct iproute2 to include all leafs on delete";
    }
    extension group-list-with-separator{
        description
            "instruct iproute2 to group all the list enteries together with the separator specified";
        argument "separator";
    }
    extension group-leafs-values-separator{
        description
            "instruct iproute2 to group the leafs values inside the list/container to be groupd with separator specified";
        argument "separator";
    }
    extension after-node-add-static-arg{
        description
            "instruct iproute2 to always add the static argument mentioned,
            for example for startcmd vrf always add type vrf after the leaf name";
        argument "static-arg";
    }
    extension add-static-arg{
        description
            "instruct iproute2 to add a static argument, to be used inside containers";
        argument "static-arg";
    }
    extension on-node-delete-or-val-false{
        description
            "when the node is deleted the provided 'arg' will be added to cmd,
            example is nomaster with removig vrf from link";
        argument "arg";
    }
    extension add_leaf_at_end{
        description
            "instruct cmdgen to add the leaf at the end of the cmd line";
    }
    extension include_parent_leafs{
        description
            "instruct cmdgen to add the leaf at the end of the cmd line";
    }
    extension not-dependency{
        description
            "this is used when the leafref is not actually a dependency, so it will not be considered in dep sorting";
    }
    extension not-cmd-arg {
        description
            "this idicate that the leaf is not an cmd_line argument, typically used for netns in modules other than links";
    }
}

module iproute2-ip-route {
    yang-version 1.1;
    namespace "urn:okda:iproute2:ip:route";
    prefix "iproute";

    import ietf-inet-types { prefix inet; }
    import okda-onmcli-extensions{ prefix onmcli; }
    import iproute2-net-types { prefix ipr2net; }
    import iproute2-cmdgen-extensions { prefix ipr2cgen; }
    import iproute2-ip-link { prefix iplink; }
    import iproute2-ip-netns { prefix ipnetns; }

    organization
        "Okda Networks";

    contact
        "Author: Ali Aqrabawi
        <aaqrabaw@okdanetworks.com>";

    description

        "This module contain the iproute2 'ip route' configurations ,
        this is module contains all IP-ROUTE(8) related configs,
        refer to https://manpages.debian.org/stretch/iproute2/ip-route.8.en.html";

    revision "2024-02-13" {
        description "Revision 1";
        reference
            "YANG model for iproute2 ip route case.";
    }

    container routes {
        description
            "ip route configuration";
        list route {
            ipr2cgen:cmd-add "ip route add";
            ipr2cgen:cmd-update "ip route replace";
            ipr2cgen:cmd-delete "ip route del";
            ipr2cgen:cmd-start;
            ipr2cgen:include-all-on-update;
            ipr2cgen:oper-cmd "ip -4 route list table all";
            ipr2cgen:oper-stop-if '{"table": ["local"]}';
            // TODO IPv6 support: oper needs to also apply "ip -6 route show"
            description
                "ip route details";
            key "prefix table metric tos netns";
            // NODE_SPEC
            leaf prefix{
                type union{
                    type inet:ip-prefix;
                    type inet:ip-address;
                    type enumeration {
                        enum "default";
                    }
                }
                ipr2cgen:value-only;
                ipr2cgen:oper-arg-name "dst";
                description
                    "ipv4 prefix";
            }
            leaf table {
                onmcli:key-default-val "main";
                ipr2cgen:oper-default-val "main";
                type union {
                    type enumeration {
                        enum "default" { value 253;}
                        enum "local" { value 255;}
                        enum "main" { value 254;}
                        enum "unspec" { value 0;}
                    }
                    type uint16;
                }
                description
                    "[254 for default] the table to add this route to. TABLEID may be a number or a string from the file
                    /etc/iproute2/rt_tables. If this parameter is omitted, ip assumes the main table,
                    with the exception of local, broadcast and nat routes, which are put into the local table by default.";

            }
            leaf metric {
                onmcli:key-default-val "0";
                ipr2cgen:oper-default-val "0";
                type uint32;
                description
                    "route metric [default 0]";
            }
            leaf tos {
                onmcli:key-default-val "default";
                ipr2cgen:oper-default-val "default";
                type ipr2net:tos;
                description
                    "the Type Of Service (TOS) key. This key has no associated mask and the longest match is
                    understood as: First, compare the TOS of the route and of the packet. If they are not equal,
                    then the packet may still match a route with a zero TOS. TOS is either an 8 bit hexadecimal
                    number or an identifier from /etc/iproute2/rt_dsfield.";
            }
            leaf netns {
                ipr2cgen:not-cmd-arg;
                onmcli:key-default-val "1";
                ipr2cgen:oper-default-val "1";
                type union {
                    type ipnetns:netns-ref;
                    type enumeration {
                        enum "1";
                    }
                }
                default "1";
                description "network namespace name";
            }
            leaf src {
                ipr2cgen:oper-arg-name "prefsrc";
                type inet:ip-address;
                description
                    "the source address to prefer when sending to the
                    destinations covered by the route prefix.";
            }
            leaf protocol {
                type enumeration {
                    enum "unspec";
                    enum "redirect";
                    enum "kernel";
                    enum "boot";
                    enum "static";
                    enum "gated";
                    enum "ra";
                    enum "mrt";
                    enum "zebra";
                    enum "bird";
                    enum "babel";
                    enum "dnrouted";
                    enum "xorp";
                    enum "ntk";
                    enum "dhcp";
                    enum "keepalived";
                    enum "bgp";
                    enum "isis";
                    enum "ospf";
                    enum "rip";
                    enum "eigrp";
                }
            }
            leaf scope {
                type enumeration {
                    enum "global";
                    enum "host";
                    enum "link";
                    enum "site";
                }
            }
            // INFO_SPEC

            /// OPTIONS
            leaf mtu {
                type ipr2net:mtu;
                description
                    "mtu value";
            }
            leaf advmss {
                type uint16{
                    range "64..9000";
                }
                description
                    "the MSS ('Maximal Segment Size') to advertise to these destinations when establishing
                    TCP connections. If it is not given, Linux uses a default value calculated from the first
                    hop device MTU. (If the path to these destination is asymmetric, this guess may be wrong.)";
            }
            /// NH
            //// NHFLAGS
            leaf flag {
                ipr2cgen:value-only;
                type enumeration {
                    enum "onlink";
                    enum "pervasive";
                }
            }
            list nexthop {
                ipr2cgen:add-static-arg "nexthop";
                ipr2cgen:oper-arg-name "nexthops";
                choice encap {
                    container mpls-encap {
                        leaf label {
                            ipr2cgen:arg-name "encap mpls";
                            ipr2cgen:oper-arg-name "not-supported";
                            type string{
                                pattern '[0-9]+(/[0-9]+)*';
                            }
                            description
                                "MPLSLABEL - mpls label stack with labels separated by /";
                        }
                    }
                    container ip-encap {
                        ipr2cgen:add-static-arg "encap ip";
                        leaf id {
                            type uint32;
                            ipr2cgen:oper-arg-name "not-supported";
                            description
                                "tunnel id";
                        }
                        leaf dst {
                            type inet:ip-prefix;
                            ipr2cgen:oper-arg-name "not-supported";
                            description
                                "remote ip";
                        }
                        leaf tos {
                            type ipr2net:tos;
                            ipr2cgen:oper-arg-name "not-supported";
                            description
                                "the Type Of Service (TOS) key. This key has no associated mask and the longest match is
                                understood as: First, compare the TOS of the route and of the packet. If they are not equal,
                                then the packet may still match a route with a zero TOS. TOS is either an 8 bit hexadecimal
                                number or an identifier from /etc/iproute2/rt_dsfield.";
                        }
                        leaf ttl {
                            type ipr2net:ttl;
                            ipr2cgen:oper-arg-name "not-supported";
                            description
                                "TTL - specifies the TTL value to use in outgoing packets.";
                            default 0;
                        }
                    }
                }
                key "dev";
                leaf dev {
                // workaround until issue #2211 in libyang is fixed
                    type union{
                        type iplink:link-ref;
                        type iplink:vti-ref;
                        type iplink:gre-ref;
                        type iplink:bridge-ref;
                        type iplink:vlan-ref;
                        type iplink:vxlan-ref;
                        type iplink:bond-ref;
                        type iplink:vrf-ref;
                    }
                    description
                        "nexthop link";
                }
                container via {
                    ipr2cgen:add-static-arg "via";
                    leaf family {
                        ipr2cgen:value-only;
                        type enumeration {
                            enum "inet";
                            enum "inet6";
                            enum "ipx";
                            enum "dnet";
                            enum "mpls";
                            enum "bridge";
                            enum "link";
                        }
                        description
                            "via address family";
                    }
                    leaf address {
                        ipr2cgen:value-only;
                        ipr2cgen:oper-arg-name "gateway";
                        // TODO IPv6 support: oper also uses "host" arg name when via family is set to inet6
                        // while using gateway when family is set to inet
                        type inet:ip-address;
                        description
                            "via address";
                    }
                }
                leaf weight {
                    type uint32;
                    description
                        "NUMBER - is a weight for this element of a multipath route
                        reflecting its relative bandwidth or quality.";
                    default 1;
                }

            }
            // Operational data
            container state {
                config false;
                leaf type{
                    type enumeration {
                        enum "unicast";
                        enum "local";
                        enum "broadcast";
                        enum "multicast";
                        enum "unreachable";
                        enum "prohibit";
                        enum "blackhole";
                        enum "nat";
                    }
                }
            }
        }
        list mpls-route {
            ipr2cgen:cmd-add "ip -M route add";
            ipr2cgen:cmd-update "ip -M route replace";
            ipr2cgen:cmd-delete "ip -M route del";
            ipr2cgen:cmd-start;
            ipr2cgen:include-all-on-update;
            ipr2cgen:oper-cmd "ip -M route list table all";
            key "label netns";
            leaf label {
                ipr2cgen:value-only;
                ipr2cgen:oper-arg-name "dst";
                type string {
                    pattern '[0-9]+(/[0-9]+)*';
                }
                description "MPLSLABLE specify the mpls label";
            }
            leaf netns {
                ipr2cgen:not-cmd-arg;
                onmcli:key-default-val "1";
                ipr2cgen:oper-default-val "1";
                type union {
                    type ipnetns:netns-ref;
                    type enumeration {
                        enum "1";
                    }
                }
                default "1";
                description "network namespace name";
            }
            leaf swap {
                ipr2cgen:arg-name "as";
                ipr2cgen:oper-arg-name "to";
                type string {
                    pattern '[0-9]+(/[0-9]+)*';
                }
                description "MPLSLABLE specify the mpls label";
            }
            leaf dev {
                type union{
                // workaround until issue #2211 in libyang is fixed
                    type iplink:link-ref;
                    type iplink:bond-ref;
                    type iplink:vti-ref;
                    type iplink:gre-ref;
                    type iplink:vrf-ref;
                    type iplink:vlan-ref;
                    type iplink:vxlan-ref;
                }
                description
                    "nexthop interface";
            }
            leaf via {
                ipr2cgen:arg-name "via inet";
                ipr2cgen:oper-arg-name "gateway";
                // TODO IPv6 support: oper also uses "host" arg name when via family is set to inet6
                // while using gateway when family is set to inet
                type inet:ip-address;
                description
                    "ipv4 nexthop address";
            }
        }
    }
}
